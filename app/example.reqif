## REQ-001
- The system shall be user-friendly.

## REQ-002
- The system shall have a login feature.

## REQ-003
- The system shall store user data securely.

## REQ-004
- The system shall support multiple languages.
